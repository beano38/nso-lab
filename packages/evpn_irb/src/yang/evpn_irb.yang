module evpn_irb {

  namespace "http://example.com/evpn_irb";
  prefix evpn_irb;

  import ietf-inet-types {prefix inet;}
  import tailf-common {prefix tailf;}
  import tailf-ncs {prefix ncs;}

  // import common service models
  import vrf { prefix vrf; }
  import bgp { prefix bgp; }
  import interface { prefix interface; }
  import evpn { prefix evpn; }
  import l2vpn {prefix l2vpn;}

  description
    "Bla bla...";

  revision 2016-01-01 {
    description
      "Initial revision.";
  }

  list evpn_irb {
    description "This is an RFS skeleton service";

    key name;
    leaf name {
      tailf:info "Unique EVPN IRB Circuit";
      type string;
    }

    uses ncs:service-data;
    ncs:servicepoint evpn_irb-servicepoint;

    leaf-list device {
      type leafref {
        path "/ncs:devices/ncs:device/ncs:name";
      }
    }

    container vrfs {
      description "VRF instances that will be configured";
      list vrf {
        key vrf_name;
        uses vrf:vrf_conf;
        uses vrf:vrf_imports;
      }
    }

    container bgp {
      description "BGP config";
      uses bgp:bgp_basic;

      list vrf {
        key vrf_name;
        uses vrf:vrf_conf;
      }
    }

    container interfaces {
        description "Interfaces that will be configured";
        list interface {
          key "interface_type interface_number";
          uses interface:basic_conf;
          uses interface:l3_conf;
          uses interface:l2_conf;
        }
    }

    container evpn {
        description "This is an RFS skeleton service";
        list evi {
          tailf:info "Unique Ethernet Virtual Identifier";
          key "evi_id";
          uses evpn:evi_conf;
        }
      }

    container l2vpn {
      leaf group_name {
        tailf:info "Bridge Group Name";
        type string;
      }
      uses l2vpn:vpls;
    }


    list pe {
      key "id";
      leaf id {
        tailf:info "Endpoint identifier";
        type string;
      }
      leaf device {
        mandatory true;
        type leafref {
          path "/ncs:devices/ncs:device/ncs:name";
        }
      }
    }
  }
}
