module olt_deploy {

  namespace "http://example.com/olt_deploy";
  prefix olt_deploy;

  import ietf-inet-types {prefix inet;}
  import tailf-common {prefix tailf;}
  import tailf-ncs {prefix ncs;}

  // import common service models
  import interface { prefix interface; }
  import evpn { prefix evpn; }
  import l2vpn {prefix l2vpn;}

  description
    "Bla bla...";

  revision 2016-01-01 {
    description
      "Initial revision.";
  }

  list olt_deploy {
    description "This is an RFS skeleton service";

    key name;
    leaf name {
      tailf:info "Unique service id";
      tailf:cli-allow-range;
      type string;
    }

    uses ncs:service-data;
    ncs:servicepoint olt_deploy-servicepoint;

    list pe {
      key "device";
    //  leaf id {
    //    tailf:info "Endpoint identifier";
    //    type string;
    //  }

      leaf device {
        mandatory true;
        type leafref {
          path "/ncs:devices/ncs:device/ncs:name";
        }
      }

      container interfaces {
        description "Interfaces that will be configured";
        list interface {
          key "interface_type interface_number";
          uses interface:basic_conf;
          uses interface:l2_conf;
          uses interface:efp_conf;
          uses interface:lacp_conf;
        }
      }
      container evpn {
        description "This is an RFS skeleton service";
        list interface {
          description "Interfaces that will be configured";
          key "interface_type interface_number";
          uses interface:basic_conf;
          uses evpn:esi_conf;
        } 
      }
      container l2vpn {
        leaf group_name {
          tailf:info "Bridge Group Name";
          type string;
        }
        uses l2vpn:vpls;
      }
    }
  }
}
