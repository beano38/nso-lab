module vrf {
  namespace "http://com/example/vrf";
  prefix vrf;

  import ietf-inet-types { prefix inet; }
  import tailf-common { prefix tailf; }
  import tailf-ncs { prefix ncs; }

  description
    "Simple package to create a VRF instance";

  revision 2019-07-08 {
    description
      "Initial revision.";
  }

  grouping vrf_conf {
    leaf vrf_name {
      tailf:info "Name of VRF Instance";
      type string;
    }
    leaf description {
      tailf:info "Description of VRF";
      type string;
    }
    leaf my_bgp_as {
      tailf:info "VRF BGP AS Number <1-65534>";
      type uint16 {
        range "1..65534";
      }
    }
    leaf my_vrf_community {
      tailf:info "VRF Community Number <1-65534>";
      type uint32 {
        range "1..65534";
      }
    }
  }

  grouping vrf_imports {
    list v4_imports {
      key vrf_community;

      leaf bgp_as {
        tailf:info "VRF BGP AS Number <1-65534>";
        type uint16 {
          range "1..65534";
        }
      }
      leaf vrf_community {
        tailf:info "VRF Community Number <1-65534>";
        type uint32 {
          range "1..65534";
          // really range is 0 to 4,294,967,295
        }
      }
    }
  }

  list vrf {
    key vrf_name;
    uses vrf:vrf_conf;

    uses ncs:service-data;
    ncs:servicepoint "vrf";

    leaf device {
      tailf:info "Device Name";
      type leafref {
        path "/ncs:devices/ncs:device/ncs:name";
      }
    }
    uses vrf:vrf_imports;
  }
}
