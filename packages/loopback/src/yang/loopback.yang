module loopback {

  namespace "http://example.com/loopback";
  prefix loopback;

  import ietf-inet-types { prefix inet; }
  import tailf-common { prefix tailf; }
  import tailf-ncs { prefix ncs; }

  description
    "Model to deploy Loopback Interfaces";

  list loopback {
    description "This is an RFS skeleton service";

    key name;
    leaf name {
      tailf:info "Device Name";
      type string;
    }

    uses ncs:service-data;
    ncs:servicepoint loopback-servicepoint;

    leaf device {
      tailf:info "Device Name";
      mandatory true;
      type leafref {
        path "/ncs:devices/ncs:device/ncs:name";
        }
      }

      list interface {
        description "Interfaces that will be configured";
        key "interface_type interface_number";
      

        leaf interface_type {
            type enumeration {
              enum "Loopback";
              enum "Bundle-Ether";
              enum "BVI";
              // enum "GigabitEthernet";
              enum "TenGigE";
            }
          }
        leaf interface_number {
          tailf:info "Interface Number";
          mandatory true;
          type string;
        }
        leaf description {
          tailf:info "Interface Description";
          type string;
        }
        leaf vrf {
          tailf:info "VRF Name";
          type string;
        }
        leaf ipv4_address {
          tailf:info "IPv4 Address";
          type inet:ipv4-address;
        }
        leaf ipv4_mask {
          tailf:info "IPv4 Netmask";
          type inet:ipv4-address;
        }
        leaf mac_address {
          tailf:info "Static MAC address of interface";
          type string;
        }
        leaf lacp_mode {
          tailf:info "Set the LACP mode on the interface";
          type enumeration {
              enum "active";
              enum "on";
              enum "passive";
            }
        }
        leaf lacp_mac_address {
          tailf:info "Static MAC address of LACP Bundle";
          type string;
        }
        leaf bundle_id {
          tailf:info "Bundle ID of Bundle-Ether Interface";
          type string;
        }
        leaf ipv6_address {
          tailf:info "IPv6 Address";
          type inet:ipv6-address;
        }
        leaf ipv6_length {
          tailf:info "IPv6 Prefix Length";
          type string;
        }
        leaf outer_vlan {
          tailf:info "VLAN ID";
          type string;
        }
        
    }
  }
}
