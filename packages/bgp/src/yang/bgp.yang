module bgp {

  namespace "http://example.com/bgp";
  prefix bgp;

  import ietf-inet-types {prefix inet;}
  import tailf-common {prefix tailf;}
  import tailf-ncs {prefix ncs;}

  // import common service models
  import vrf { prefix vrf; }

  description
    "Bla bla...";

  revision 2016-01-01 {
    description
      "Initial revision.";
  }

  grouping bgp_basic {
    leaf bgp_as {
      tailf:info "BGP AS Number <1-65534>";
      type uint16 {
        range "1..65534";
      }
    }
  }

  list bgp {
    description "This is an RFS skeleton service";

    key name;
    leaf name {
      tailf:info "Unique service id";
      tailf:cli-allow-range;
      type string;
    }

    uses ncs:service-data;
    ncs:servicepoint bgp-servicepoint;

    leaf device {
      tailf:info "Device Name";
      type leafref {
        path "/ncs:devices/ncs:device/ncs:name";
      }
    }
    uses bgp:bgp_basic;

    list vrf {
      key vrf_name;
      uses vrf:vrf_conf;
    }
  }
}
