module evpn {

  namespace "http://example.com/evpn";
  prefix evpn;

  import ietf-inet-types {prefix inet;}
  import tailf-common {prefix tailf;}
  import tailf-ncs {prefix ncs;}

  // import common service models
  import interface { prefix interface; }

  description
    "Bla bla...";

  revision 2016-01-01 {
    description
      "Initial revision.";
  }

  grouping evi_conf {
    leaf evi_id {
      type uint16 {
        range "1..65534";
      }
    }
  }

  grouping esi_conf {
    leaf esi_identifier {
        tailf:info "Ethernet Segment Identifier";
        type string;
    }
  }


  list evpn {
    description "This is an RFS skeleton service";

    key name;
    leaf name {
      tailf:info "Unique service id";
      tailf:cli-allow-range;
      type string;
    }

    uses ncs:service-data;
    ncs:servicepoint evpn-servicepoint;

    leaf device {
      tailf:info "Device Name";
      type leafref {
        path "/ncs:devices/ncs:device/ncs:name";
      }
    }

    list evi {
      tailf:info "Unique Ethernet Virtual Identifier";
      key "evi_id";

      uses evpn:evi_conf;
    }

    list interface {
      description "Interfaces that will be configured";
      key "interface_type interface_number";
    
      uses interface:basic_conf;

      uses evpn:esi_conf;
      
    } 
  }
}
