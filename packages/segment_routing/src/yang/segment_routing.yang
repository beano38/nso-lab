module segment_routing {

  namespace "http://example.com/segment_routing";
  prefix segment_routing;

  import ietf-inet-types {prefix inet;}
  import tailf-common {prefix tailf;}
  import tailf-ncs {prefix ncs;}

  description
    "Segment Routing Configuration";

  list segment_routing {
    description "This is an RFS skeleton service";

    key name;
    leaf name {
      tailf:info "Unique service id";
      tailf:cli-allow-range;
      type string;
    }

    uses ncs:service-data;
    ncs:servicepoint segment_routing-servicepoint;

    // may replace this with other ways of refering to the devices.
    leaf device {
      type leafref {
        path "/ncs:devices/ncs:device/ncs:name";
      }
    }

    list interface {
      description "Interfaces that will be configured";
      key "interface_type interface_number";

      leaf interface_type {
        type enumeration{
          enum "FastEthernet";
          enum "GigabitEthernet";
          enum "TenGigE";
          enum "HundredGigE";
          enum "Loopback";
        }
      }
      leaf interface_number {
        tailf:info "Interface Number, example 0/1";
        type string;
      }
      leaf sid {
        tailf:info "Prefix SID";
        type string;
      }
      leaf ip_addr {
        tailf:info "Loopback0 IP Address";
        type string;
      }
      leaf ti_lfa {
        tailf:info "Enable Topology Independent LFA";
        type boolean;
        default false;
      }
      // container bfd {
      // tailf:info "BFD Configuration Options";
      //   leaf enabled {
      //     tailf:info "Enable BFD";
      //     type boolean;
      //     default false;
      //   }
      //   leaf interval {
      //     tailf:info "Interval in microseconds, default 15";
      //     when "boolean(../enabled)";
      //     type string;
      //     default "15";
      //   }
      //   leaf multiplier {
      //     tailf:info "BFD Multiplier, default 3";
      //     when "boolean(../enabled)";
      //     type string;
      //     default "3";
      //   }
      // }
    }


    container isis {
      description "ISIS parameters";
      leaf process_name {
        tailf:info "ISIS Process Name";
        mandatory true;
        type string;
      }
      leaf sr_prefer {
        tailf:info "Prefer SR Labels over LDP Labels";
        type boolean;
        default false;
      }
    }
  }
}
